# -*- coding: utf-8 -*-
"""Lead designer panel: build a set of leads, check they fit, look at them.

WHAT IT IS FOR
--------------
Someone who wants to know whether two 8-contact leads straddling the midline
will both sit in the dorsal epidural space at T11, or whether a 4-contact lead
can be threaded out to the left third ganglion without cutting into it, should
not have to know that the midline is x = 56.60, that the canal centre follows a
cubic in z, or that a foramen is measured by alternating ray casts. This panel
is those questions with spinboxes on them:

    add the leads you want and set the numbers   ->  Check fit
    a green PASS or a red FAIL per lead AND for the set, with the actual
    measurements, in words
    Show leads (a toggle)                        ->  see them in the document
    Export STLs                                  ->  generated_leads/<name>/

No coordinates and no centreline polynomials appear anywhere in the interface.

THERE IS NO CONFIGURATION LIST
------------------------------
There used to be a dropdown of named configurations at the top of this panel,
backed by a `configs:` section in the YAML that grew an entry every time a lead
was positioned. Both are gone. You dial the parameters in and go; everything is
custom, and nothing has to be named before it can be looked at. What the YAML
still holds -- lead_defaults.yaml -- is the STARTING VALUES a new lead opens
with, the vertebral levels, and how many leads of one type are allowed.

The one thing that still pins two exact placements is src/freecad/
test_regression.py, which rebuilds the two committed 8-contact leads from
parameters written out inside it and asserts their 18 STLs come back byte for
byte. That is a test, not a catalogue, and this panel does not read it.

THREE TYPES OF LEAD, AND UP TO max_leads_per_type OF EACH
---------------------------------------------------------
Add a dorsal, a ventral or a DRG lead with the buttons at the top; each gets its
own tab of parameters, and lead_defaults.yaml's max_leads_per_type (2 by
default) is what the Add buttons stop at. The parameters differ by type because
the geometry problems differ: a dorsal or ventral lead runs rostro-caudally
along the canal and is positioned by a vertebral level and an offset from the
midline, while a DRG lead runs LATERALLY out through a neuroforamen and is
positioned by naming a ganglion. The panel shows one set of controls or the
other, never both.

CHECK FIT ANSWERS TWO QUESTIONS
-------------------------------
Each lead's own verdict -- does it fit its channel, is it inside the right
tissue, does it clear the ganglion -- and then the set's, which is the one no
single lead can answer: do any two of them occupy the same space. Two leads 1 mm
apart both fit the epidural space perfectly well and still cannot both be
implanted, so the banner is red if either kind of check fails.

INSTALL
-------
    MDIR=$(python3 -c 'import FreeCAD,os;print(os.path.join(FreeCAD.getUserAppDataDir(),"Macro"))')
    mkdir -p "$MDIR"
    ln -sfn "$PWD/src/freecad/lead_designer.FCMacro" "$MDIR/lead_designer.FCMacro"

    # FreeCAD's macro directory is VERSIONED -- on 26.3 it is
    #   ~/.local/share/FreeCAD/v26-3/Macro/
    # not ~/.local/share/FreeCAD/Macro/, which FreeCAD ignores entirely. Ask it
    # rather than guessing, because the path moves with the version:
    #
    #   python3 -c "import FreeCAD, os; print(os.path.join(FreeCAD.getUserAppDataDir(), 'Macro'))"
    #
    # Then, in FreeCAD: Macro -> Macros... -> select this file -> Execute.

then Macro -> Macros... -> lead_designer -> Execute. Worth putting on a toolbar
the same way as tissue_visibility.FCMacro: Tools -> Customize -> Macros, then
Tools -> Customize -> Toolbars. That same dialog is where its icon is set: pick
this macro under Tools -> Customize -> Macros, click the Pixmap "..." button,
Add icons..., and choose src/freecad/icons/lead_designer.svg (or
lead_designer_32.png if the picker refuses SVG). src/freecad/README.md has the
full six steps. Re-running re-uses the same dock rather than stacking copies;
close it with the dock's own X.

Like tissue_visibility.FCMacro this needs the repo on disk -- it imports
build_lead_config, which is where all the actual work lives. REPO below is the
default; set SCS_MODELING_REPO if the checkout moves.

THE PREVIEW IS ONE TOGGLE, AND NOTHING HERE EVER SAVES
------------------------------------------------------
"Show leads" is a single checkable button, green while the leads are in the
document. Pressing it builds every lead of the set into the ACTIVE DOCUMENT as
ordinary parametric bodies inside one group labelled "13 SCS Leads"; pressing it
again deletes them and puts the tree back exactly as it was. Showing and hiding
were two buttons once, which meant the interface never said which state you were
in -- the button now IS the state.

That is the whole design: there is ONE model document, NBF_RADO-SCS.FCStd,
holding anatomy only -- the extended T6-T12 model, 503 bodies, no lead of any
kind -- and a lead is a handful of numbers plus a directory of STLs.

THE CHECKS DO NOT READ THE DOCUMENT. Fit, containment and DRG checks load the
anatomy as STL files from disk (src/freecad/anatomy.py): by default the
extended model's separate bodies in fem/out/geometry/rado_up4, the same bodies
the document shows and the source of the fused set the FEM meshes. Levels
T6-T12 come from lead_defaults.yaml; ganglia L1_T6 .. R1_T9 are the extended
levels' copies of L1 and R1. Trying ten arrangements must
not mean ten copies of a 25 MB document. Explore, export the one you want, and
close the document WITHOUT SAVING.

This macro contains no save of any kind and must not grow one. A FreeCAD
document saved with no GUI running loses every ShapeAppearance in it; the panel
runs inside the GUI so that is not the failure mode here, but the rule that
nothing in this pipeline saves a model document except deliberately, by hand, is
what keeps the tissue colours alive. See make_tissue_groups.py.

WHY IT BLOCKS WHILE CHECKING
----------------------------
Checking a fit ray casts a few thousand points against several meshes and takes
two to ten seconds, more for a DRG lead than an epidural one because a foramen
is measured by iterating two ray casts rather than one. It runs on the GUI
thread with a wait cursor rather than in a worker, deliberately: FreeCAD's
document API is not thread-safe, the meshes have to be loaded in the same
interpreter, and a few seconds of freeze on a button press is a far smaller
problem than a background thread mutating a document while the user clicks in
the tree.
"""
import json
import os
import sys
import traceback

import FreeCAD
import FreeCADGui

try:
    from PySide import QtCore, QtGui, QtWidgets
except ImportError:                                     # pragma: no cover
    try:
        from PySide6 import QtCore, QtGui, QtWidgets
    except ImportError:
        from PySide2 import QtCore, QtGui, QtWidgets

REPO = os.environ.get("SCS_MODELING_REPO",
                      os.path.expanduser("~/Projects/SCS-Modeling"))
OBJECT_NAME = "SCS_LeadDesignerDock"       # so a second run re-uses the dock

CUSTOM = "— custom —"

# Colours for the verdict banner. Deliberately not the tissue colours: this is
# interface chrome, and nothing in this file may imply a material.
BANNER = {"PASS": ("#1b5e20", "#c8e6c9"),
          "WARN": ("#7a4f01", "#ffe0b2"),
          "FAIL": ("#8e0000", "#ffcdd2")}

# The "Show leads" toggle, checked. A mid green dark enough for white text to
# clear 4.5:1, which is what makes it readable on both FreeCAD themes -- the
# checked state paints its OWN background and text rather than tinting the
# theme's, so it cannot end up as light-grey-on-light-green under one stylesheet
# and unreadable under another.
TOGGLE_ON_BG = "#2e7d32"
TOGGLE_ON_HOVER = "#388e3c"
TOGGLE_ON_BORDER = "#1b5e20"
TOGGLE_ON_FG = "#ffffff"

TYPE_WORDS = {"dorsal": "Dorsal epidural", "ventral": "Ventral epidural",
              "drg": "DRG (foraminal)"}


def load_builder():
    """Import build_lead_config from the repo. Everything real lives there."""
    freecad_dir = os.path.join(REPO, "src", "freecad")
    if freecad_dir not in sys.path:
        sys.path.insert(0, freecad_dir)
    import build_lead_config
    # Reloaded on every run so editing the module and re-executing the macro
    # picks the change up; a stale copy that silently ignores your edits is a
    # miserable way to spend an afternoon.
    try:
        import importlib
        importlib.reload(build_lead_config)
        if "make_scs_lead" in sys.modules:
            importlib.reload(sys.modules["make_scs_lead"])
    except Exception:
        pass
    return build_lead_config


def load_reader():
    """Import read_document_leads, which recovers parameters from a document."""
    freecad_dir = os.path.join(REPO, "src", "freecad")
    if freecad_dir not in sys.path:
        sys.path.insert(0, freecad_dir)
    import read_document_leads
    try:
        import importlib
        importlib.reload(read_document_leads)
    except Exception:
        pass
    return read_document_leads


def worst_of(levels):
    if "FAIL" in levels:
        return "FAIL"
    return "WARN" if "WARN" in levels else "PASS"


class LeadPage(QtWidgets.QWidget):
    """The parameters of ONE lead. Which controls exist depends on its type.

    A page owns no geometry and no verdict; it is a form that produces the
    parameter dict build_lead_config.resolve_lead() layers on top of
    lead_defaults.yaml. Keeping it that dumb is what stops the panel and the
    command line from drifting apart -- both go through the same resolve.
    """

    changed = QtCore.Signal()

    def __init__(self, panel, kind):
        super(LeadPage, self).__init__()
        self.panel = panel
        self.kind = kind
        self.loading = False

        form = QtWidgets.QFormLayout(self)
        form.setLabelAlignment(QtCore.Qt.AlignRight)

        # THE HARDWARE CONTROLS ARE ALWAYS BUILT; FOR A DRG LEAD THEY ARE
        # DISABLED AND SHOW RADO'S OWN NUMBERS.
        #
        # A dorsal or ventral lead is generated, so its contact count, contact
        # length, gap, diameter and tail are real parameters and are editable.
        # A DRG lead is a rigid COPY of the four-contact lead RADO ships, so
        # those five are properties of RADO's meshes and nothing can change
        # them.
        #
        # An earlier version omitted the five rows entirely on a DRG page, on
        # the reasoning that a greyed-out spinbox still reads as "a setting,
        # just not now". Mohamed asked for the opposite and he is right: with
        # the rows absent, the only way to find out what RADO's lead actually
        # IS was to read a sentence, and the only way to discover the values
        # were fixed was to try to set one and get an error back. Showing the
        # real numbers, greyed out, answers both questions before they are
        # asked. Errors are a bad way to teach an interface's rules.
        #
        # The values come from RADO's meshes via show_hardware(), never from a
        # literal, so the panel cannot display one thing while the geometry is
        # another.
        self.contacts = self.spin_int("How many electrode contacts", 1, 32)
        form.addRow("Contacts", self.contacts)
        self.contact_length = self.spin("Length of each contact", 0.25, 20.0,
                                        0.25, " mm")
        form.addRow("Contact length", self.contact_length)
        self.gap = self.spin("Insulator between neighbouring contacts", 0.0,
                             20.0, 0.25, " mm")
        form.addRow("Gap", self.gap)
        self.diameter = self.spin("Lead diameter. Khadka et al. use 1.25 mm; "
                                  "the house default is 1.30 mm",
                                  0.2, 4.0, 0.05, " mm")
        form.addRow("Diameter", self.diameter)
        self.contact_thickness = self.spin(
            "How far each electrode contact projects radially beyond the "
            "insulated lead body. Contact outer diameter = Diameter + twice "
            "this value. Zero gives the legacy flush contact.",
            0.0, 2.0, 0.01, " mm")
        form.addRow("Contact thickness", self.contact_thickness)
        if kind == "drg":
            self.contact_thickness.setSpecialValueText("Fixed mesh")
            self.contact_thickness.setValue(self.contact_thickness.minimum())
        self.tail = self.spin("Plain insulator beyond the end contacts", 0.0,
                              30.0, 0.5, " mm")
        form.addRow("Tail", self.tail)

        if kind == "drg":
            fixed_tip = ("Fixed by RADO's meshes. A DRG lead is a rigid copy of "
                         "the lead this model ships, so this is measured, not "
                         "chosen. Only the target and the three nudges are yours.")
            for w in (self.contacts, self.contact_length, self.gap,
                      self.diameter, self.contact_thickness, self.tail):
                w.setEnabled(False)
                w.setToolTip(fixed_tip)
                # Three decimals, not the two a swept lead uses. These are
                # measurements off RADO's meshes, and rounding 1.251 mm to
                # 1.25 in a box captioned "measured" would be a small lie.
                if hasattr(w, "setDecimals"):
                    w.setDecimals(3)

        if kind == "drg":
            self.hardware_note = QtWidgets.QLabel("")
            self.hardware_note.setWordWrap(True)
            self.hardware_note.setStyleSheet("color: gray;")
            self.hardware_note.setToolTip(
                "A DRG lead is not built here -- it is RADO's own four-contact "
                "lead, the five STLs in STL_files/, rigidly transformed onto "
                "the ganglion you pick. Its contacts cannot be resized, so "
                "there are no spinboxes for them. These numbers are measured "
                "back off those meshes.")
            form.addRow("Hardware", self.hardware_note)
            self.show_hardware()

            self.target = QtWidgets.QComboBox()
            self.target.addItems(panel.ganglia)
            self.target.setToolTip(
                "Which dorsal root ganglion. L is the patient's LEFT, R the "
                "right, numbered rostral to caudal within each side. These are "
                "the model's own ganglion numbers, NOT lumbar levels.")
            self.target.currentIndexChanged.connect(self.touched)
            form.addRow("Target ganglion", self.target)

            # The three nudges, all in the TARGET GANGLION'S own frame, which
            # is what makes them mean the same thing on the right side as on
            # the left -- rostral is rostral at every ganglion, even though
            # reaching a right one involved a reflection. Zero on all three
            # means "exactly where RADO put it relative to its ganglion", which
            # is the placement Mohamed called correct, so zero is the default
            # and any other value is a deliberate departure from it.
            self.lateral_offset = self.spin(
                "Slide the lead along the root. Positive is further OUT "
                "(distal). Zero puts the array exactly where RADO's sits "
                "relative to its own ganglion.", -10.0, 15.0, 0.5, " mm")
            form.addRow("Along the root", self.lateral_offset)

            self.y_offset = self.spin(
                "Nudge across the foramen. Positive is DORSAL (posterior). "
                "Zero keeps RADO's own relationship to the ganglion.",
                -4.0, 4.0, 0.25, " mm")
            form.addRow("Nudge dorsal/ventral", self.y_offset)
            self.z_offset = self.spin(
                "Nudge along the spine. Positive is ROSTRAL (towards the head) "
                "on EITHER side. Use this if the fit check reports the lead "
                "too close to the ganglion here.", -6.0, 6.0, 0.25, " mm")
            form.addRow("Nudge rostral/caudal", self.z_offset)

            self.ganglion_note = QtWidgets.QLabel("")
            self.ganglion_note.setWordWrap(True)
            self.ganglion_note.setStyleSheet("color: gray;")
            form.addRow("", self.ganglion_note)
            self.target.currentIndexChanged.connect(self.describe_target)

            self.numeric = (self.lateral_offset, self.y_offset, self.z_offset)
        else:
            self.level = QtWidgets.QComboBox()
            self.level.addItem(CUSTOM)
            self.level.addItems(list(panel.cfg["levels"]))
            self.level.setToolTip("Vertebral level for the centre of the contact "
                                  "array. Level names are RADO's own -- see the "
                                  "caveat in lead_defaults.yaml.")
            self.level.currentIndexChanged.connect(self.level_picked)
            form.addRow("Level", self.level)

            self.z_center = self.spin("Rostro-caudal position of the middle of the "
                                      "contact array. Set by the level above, or "
                                      "type it directly.", 0.0, 300.0, 1.0, " mm")
            self.z_center.valueChanged.connect(self.z_edited)
            form.addRow("Position (rostro-caudal)", self.z_center)

            self.x_offset = self.spin(
                "Medial-lateral offset from the midline. POSITIVE is the patient's "
                "LEFT, negative is the right, zero is on the midline.",
                -10.0, 10.0, 0.5, " mm")
            self.x_offset.valueChanged.connect(self.describe_offset)
            form.addRow("Offset from midline", self.x_offset)

            self.offset_note = QtWidgets.QLabel("")
            self.offset_note.setStyleSheet("color: gray;")
            form.addRow("", self.offset_note)

            self.numeric = (self.contacts, self.contact_length, self.gap,
                            self.diameter, self.contact_thickness, self.tail, self.z_center, self.x_offset)

        for w in self.numeric:
            w.valueChanged.connect(self.touched)

    # -- widget helpers ---------------------------------------------------
    def spin(self, tip, lo, hi, step, suffix):
        w = QtWidgets.QDoubleSpinBox()
        w.setRange(lo, hi)
        w.setSingleStep(step)
        w.setDecimals(2)
        w.setSuffix(suffix)
        w.setToolTip(tip)
        return w

    def spin_int(self, tip, lo, hi):
        w = QtWidgets.QSpinBox()
        w.setRange(lo, hi)
        w.setToolTip(tip)
        return w

    def touched(self, *_a):
        if not self.loading:
            self.changed.emit()

    def level_picked(self, _i=None):
        """Picking a level drives the position box; typing a position clears it."""
        if self.loading:
            return
        name = self.level.currentText()
        if name != CUSTOM:
            self.loading = True
            try:
                # A ventral lead reaches the extended levels at a different z
                # (lead_defaults.yaml, ventral_levels).
                self.z_center.setValue(self.panel.blc.level_z(self.panel.cfg, self.kind, name))
            finally:
                self.loading = False
        self.touched()

    def z_edited(self, *_a):
        """A hand-typed position means the level combo no longer describes it."""
        if self.loading:
            return
        if self.level.currentText() != CUSTOM:
            self.loading = True
            try:
                self.level.setCurrentText(CUSTOM)
            finally:
                self.loading = False

    def describe_offset(self, *_a):
        dx = self.x_offset.value()
        if abs(dx) < 0.005:
            self.offset_note.setText("on the midline")
        else:
            self.offset_note.setText("%.2f mm to the patient's %s"
                                     % (abs(dx), "LEFT" if dx > 0 else "RIGHT"))

    def show_hardware(self):
        """Fill the DRG page's read-only hardware line, from RADO's own meshes.

        Measured rather than quoted, by the same call resolve_lead() makes, so
        the panel cannot tell the user one thing while the geometry is another.
        If the STLs cannot be read the line says so instead of guessing --
        there is no fallback set of numbers to fall back to, which is the point
        of this type of lead.
        """
        try:
            hw = self.panel.blc.rado_drg_hardware()
        except Exception as exc:
            self.hardware_note.setText(
                "RADO's lead STLs could not be read (%s), so a DRG lead cannot "
                "be built." % exc)
            return
        # Put the real numbers into the five disabled spinboxes, so the page
        # shows what RADO's lead IS rather than leaving them at a swept lead's
        # defaults. Measured here, never hardcoded.
        for widget, key in ((self.contacts, "contacts"),
                            (self.contact_length, "contact_length"),
                            (self.gap, "gap"),
                            (self.diameter, "diameter"),
                            (self.tail, "tail")):
            was = widget.blockSignals(True)
            if key == "contacts":
                widget.setValue(int(hw[key]))
            else:
                widget.setValue(float(hw[key]))
            widget.blockSignals(was)

        self.hardware_note.setText(
            "Above is RADO's own hardware, measured off its meshes and FIXED. "
            "A DRG lead is a rigid copy of the lead this model ships, so there "
            "is nothing there to resize. Only the target and the three nudges "
            "below are yours.")

    def describe_target(self, *_a):
        g = self.panel.foramen.get(self.target.currentText()) if self.panel.foramen else None
        if not g:
            self.ganglion_note.setText("")
            return
        where = ("a copy of %s at the %s level (extended model), " % (g["copy_of"], g["level"])
                 if g.get("copy_of") else "")
        self.ganglion_note.setText(
            "%s side, %sganglion centre %.1f mm from the midline; the foramen is a "
            "measurable channel from %.1f to %.1f mm out."
            % (g["side"], where, g["ganglion_u_centre"], g["usable_u"][0], g["usable_u"][1]))

    # -- reading and writing ----------------------------------------------
    def load(self, params):
        self.loading = True
        try:
            if self.kind == "drg":
                self.target.setCurrentText(str(params["target"]))
                self.lateral_offset.setValue(float(params.get("lateral_offset", 0.0)))
                self.y_offset.setValue(float(params.get("y_offset", 0.0)))
                self.z_offset.setValue(float(params.get("z_offset", 0.0)))
            else:
                self.contacts.setValue(int(params["contacts"]))
                self.contact_length.setValue(float(params["contact_length"]))
                self.gap.setValue(float(params["gap"]))
                self.diameter.setValue(float(params["diameter"]))
                self.contact_thickness.setValue(float(params.get("contact_thickness", 0.0)))
                self.tail.setValue(float(params["tail"]))
                self.z_center.setValue(float(params["z_center"]))
                self.x_offset.setValue(float(params["x_offset"]))
                self.level.setCurrentText(params.get("level") or CUSTOM)
        finally:
            self.loading = False
        if self.kind == "drg":
            self.describe_target()
        else:
            self.describe_offset()

    def overrides(self):
        """This page as the parameter dict resolve_lead() understands."""
        out = {"type": self.kind}
        if self.kind == "drg":
            # No hardware keys at all. resolve_lead() REJECTS contacts,
            # contact_length, gap, diameter and tail on a DRG lead, so sending
            # them -- even set to RADO's own measured values -- would be an
            # error, and rightly: the panel would be asking for geometry it
            # does not get to choose.
            out.update(target=self.target.currentText(),
                       lateral_offset=self.lateral_offset.value(),
                       y_offset=self.y_offset.value(),
                       z_offset=self.z_offset.value())
        else:
            out.update(contacts=self.contacts.value(),
                       contact_length=self.contact_length.value(),
                       gap=self.gap.value(),
                       diameter=self.diameter.value(),
                       contact_thickness=self.contact_thickness.value(),
                       tail=self.tail.value(),
                       z_center=self.z_center.value(),
                       x_offset=self.x_offset.value())
            if self.level.currentText() != CUSTOM:
                out["level"] = self.level.currentText()
        return out


class LeadDesigner(QtWidgets.QWidget):
    """The dock's contents: a set of leads, a verdict for each and for the set."""

    def __init__(self, blc):
        super(LeadDesigner, self).__init__()
        self.blc = blc
        self.rdl = load_reader()
        self.cfg = blc.parse_defaults_file(blc.DEFAULTS_YAML)
        self.max_per_type = int(self.cfg.get("max_leads_per_type",
                                             blc.DEFAULT_MAX_LEADS_PER_TYPE))
        try:
            self.foramen = blc.load_foramen_corridors()["ganglia"]
        except Exception:
            self.foramen = {}
        # Left then right, each rostral to caudal: L1_T6 .. L1_T9, L1 .. L4.
        self.ganglia = sorted(self.foramen, key=lambda t: (
            self.foramen[t]["side"] != "left", -self.foramen[t]["ganglion_centroid"][2])) or ["L3"]

        self.meshes = None                  # loaded lazily; several MB of STL
        self.outcome = None                 # last validation, for Preview/Export
        self.leads = None                   # the resolved parameter sets
        self.loading = False

        outer = QtWidgets.QVBoxLayout(self)
        outer.setContentsMargins(6, 6, 6, 6)
        outer.setSpacing(6)

        # -- the leads ----------------------------------------------------
        add = QtWidgets.QHBoxLayout()
        add.addWidget(QtWidgets.QLabel("Add lead:"))
        self.add_buttons = {}
        for kind in ("dorsal", "ventral", "drg"):
            btn = QtWidgets.QPushButton(TYPE_WORDS[kind].split(" ")[0])
            btn.setToolTip("Add a %s lead to the set. At most %d of each type."
                           % (TYPE_WORDS[kind].lower(), self.max_per_type))
            btn.clicked.connect(lambda _c=False, k=kind: self.add_lead(k))
            add.addWidget(btn)
            self.add_buttons[kind] = btn
        self.btn_remove = QtWidgets.QPushButton("Remove this lead")
        self.btn_remove.setToolTip("Remove the lead whose tab is showing.")
        self.btn_remove.clicked.connect(self.remove_lead)
        add.addWidget(self.btn_remove)
        outer.addLayout(add)

        self.tabs = QtWidgets.QTabWidget()
        self.tabs.setDocumentMode(True)
        outer.addWidget(self.tabs)

        # -- verdict -------------------------------------------------------
        self.banner = QtWidgets.QLabel("Not checked yet")
        self.banner.setAlignment(QtCore.Qt.AlignCenter)
        self.banner.setMinimumHeight(28)
        self.set_banner(None, "Not checked yet")
        outer.addWidget(self.banner)

        self.detail = QtWidgets.QTextEdit()
        self.detail.setReadOnly(True)
        self.detail.setLineWrapMode(QtWidgets.QTextEdit.WidgetWidth)
        self.detail.setMinimumHeight(180)
        mono = QtGui.QFont("monospace")
        mono.setStyleHint(QtGui.QFont.TypeWriter)
        self.detail.setFont(mono)
        outer.addWidget(self.detail, 1)

        # -- actions -------------------------------------------------------
        row1 = QtWidgets.QHBoxLayout()
        self.btn_check = QtWidgets.QPushButton("Check fit")
        self.btn_check.setToolTip("Measure the space every lead would sit in, test "
                                  "every point on each lead's surface for being "
                                  "inside it, and measure the leads against each "
                                  "other. Takes a few seconds.")
        self.btn_check.clicked.connect(self.check)
        row1.addWidget(self.btn_check, 2)

        # ONE button for the leads being in the document or not, because that
        # is one piece of state and two buttons could never show which way it
        # was. Checked and green: they are in the tree, under "13 SCS Leads".
        self.btn_preview = QtWidgets.QPushButton("Show leads")
        self.btn_preview.setCheckable(True)
        self.btn_preview.setMinimumHeight(26)
        self.btn_preview.setStyleSheet(self.toggle_style())
        self.btn_preview.setToolTip(
            "Put every lead into the active document, in one group called "
            "\"13 SCS Leads\". Press again to take them out. They are "
            "disposable — do not save the document for them.")
        self.btn_preview.toggled.connect(self.preview_toggled)
        row1.addWidget(self.btn_preview, 1)
        outer.addLayout(row1)

        row2 = QtWidgets.QHBoxLayout()
        self.btn_export = QtWidgets.QPushButton("Export STLs")
        self.btn_export.setToolTip("Write one STL per contact plus the insulator, "
                                   "for every lead, to generated_leads/. Only "
                                   "offered for a set that fits.")
        self.btn_export.clicked.connect(self.do_export)
        row2.addWidget(self.btn_export, 1)
        outer.addLayout(row2)

        self.status = QtWidgets.QLabel("")
        self.status.setWordWrap(True)
        self.status.setStyleSheet("color: gray;")
        outer.addWidget(self.status)

        if not self.hydrate_from_document():
            self.add_lead("dorsal")
        self.sync_preview_button()

    # -- the set of pages --------------------------------------------------
    def pages(self):
        return [self.tabs.widget(i) for i in range(self.tabs.count())]

    def count_of(self, kind):
        return sum(1 for p in self.pages() if p.kind == kind)

    def retitle(self):
        """Tab labels carry the lead number, which is what the bodies in the
        tree and the exported subdirectories are named for, so they agree:
        tab "2  DRG (foraminal)" is "lead 2 (drg) — contact 03" in the tree and
        lead2_drg_L3/ on disk."""
        for i, page in enumerate(self.pages(), start=1):
            self.tabs.setTabText(i - 1, "%d  %s" % (i, TYPE_WORDS[page.kind]))
        for kind, btn in self.add_buttons.items():
            btn.setEnabled(self.count_of(kind) < self.max_per_type)
        self.btn_remove.setEnabled(self.tabs.count() > 1)

    # A recovered z_center is a measured number, but it usually lands on a
    # named vertebral level -- the poster dorsal leads sit at 80.440, and
    # lead_defaults.yaml puts T12 at 80.44. Showing "— custom —" there would
    # hide the one fact a clinician reads first. The levels are tens of mm
    # apart, so this tolerance cannot confuse two of them; it only has to
    # absorb the recovery's own error (~0.02 mm, measured).
    LEVEL_MATCH_MM = 0.1

    def level_for_z(self, z, kind="dorsal"):
        """Name the vertebral level a recovered z_center sits at, else CUSTOM."""
        best, best_d = None, self.LEVEL_MATCH_MM
        for name in (self.cfg.get("levels") or {}):
            try:
                d = abs(self.blc.level_z(self.cfg, kind, name) - float(z))
            except (TypeError, ValueError):
                continue
            if d <= best_d:
                best, best_d = name, d
        return best or CUSTOM

    def hydrate_from_document(self):
        """Fill the panel from the leads already in the active document.

        Opening a RADO model that carries leads used to show this panel's
        DEFAULTS, which described nothing in front of you -- the poster dorsal
        model has two leads at +/-2.00 mm, 1.60 mm across, centred at z = 80.44,
        against a default of one lead on the midline, 1.30 mm across, at z = 110.
        Editing from that state would have silently moved real leads.

        The parameters are not stored in the document (the lead bodies carry
        only Placement/Shape/Label/Visibility), so read_document_leads recovers
        them from the geometry, and the vertebral level is named back from the
        recovered position (the poster dorsal leads sit at 80.440 = T12).
        contact_thickness is not encoded anywhere and keeps its default, so a
        page is always complete.

        Returns True when at least one lead was loaded.
        """
        doc = FreeCAD.ActiveDocument
        if doc is None:
            return False
        try:
            found = self.rdl.recover(doc, midline_x=self.blc.MIDLINE_X)
        except Exception:
            FreeCAD.Console.PrintWarning(
                "Lead designer: could not read the document's leads, starting "
                "from defaults.\n%s\n" % traceback.format_exc())
            return False
        if not found:
            return False

        loaded, stale = 0, []
        self.loading = True
        try:
            for rec in found:
                kind = rec["type"]
                if self.count_of(kind) >= self.max_per_type:
                    continue
                # Start from the resolved defaults so every key a page reads is
                # present, then overlay only what the geometry actually gave us.
                params = self.blc.resolve_lead(self.cfg, {"type": kind},
                                               self.tabs.count() + 1, 1)
                for key in rec["_recovered"]:
                    params[key] = rec[key]
                params["level"] = self.level_for_z(params["z_center"], kind)
                if self.add_lead(kind, params) is not None:
                    loaded += 1
                    if rec["_label_type"] is None:
                        stale.append(rec["_lead_number"])
        finally:
            self.loading = False

        if not loaded:
            return False
        msg = ("Loaded %d lead(s) from %s. Values are recovered from the lead "
               "geometry -- the file does not store them -- and the level is "
               "named when the recovered position matches one. Contact "
               "thickness is not recoverable and keeps its default."
               % (loaded, doc.Name))
        if stale:
            msg += (" Lead(s) %s carry no type in their label and were assumed "
                    "dorsal -- check before rebuilding."
                    % ", ".join(str(n) for n in stale))
        self.status.setText(msg)
        return True

    def add_lead(self, kind, params=None):
        if self.count_of(kind) >= self.max_per_type:
            self.status.setText(
                "At most %d %s leads at once (max_leads_per_type in "
                "lead_defaults.yaml)." % (self.max_per_type, kind))
            return None
        page = LeadPage(self, kind)
        if params is None:
            params = self.blc.resolve_lead(self.cfg, {"type": kind},
                                           self.tabs.count() + 1, 1)
        page.load(params)
        page.changed.connect(self.parameters_changed)
        self.tabs.addTab(page, "")
        self.tabs.setCurrentWidget(page)
        self.retitle()
        if not self.loading:
            self.parameters_changed()
        return page

    def remove_lead(self):
        if self.tabs.count() <= 1:
            return
        self.tabs.removeTab(self.tabs.currentIndex())
        self.retitle()
        self.parameters_changed()

    # -- reading and writing the form -------------------------------------
    def parameters_changed(self, *_a):
        """Any edit invalidates the last check, and dates any shown leads.

        The leads in the tree are NOT rebuilt here. Rebuilding means re-running
        the fit check, which takes seconds, and doing that on every keystroke in
        a spinbox would make the panel unusable. The toggle is how you ask for
        it: the status line says so, and turning it off and on again rebuilds
        from the numbers now on screen.
        """
        if self.loading:
            return
        self.outcome = None
        self.set_banner(None, "Not checked yet")
        if self.btn_preview.isChecked():
            self.status.setText("The leads in the tree are the previous numbers. "
                                "Press \u201cShow leads\u201d twice to rebuild them.")

    def resolve(self):
        """The tabs as a list of resolved leads.

        Resolved through build_lead_config.resolve_leads() rather than
        assembled here, so the panel cannot drift from what the command line
        does: the layering onto lead_defaults.yaml, the per-type parameter
        rules and the max_leads_per_type cap all happen in exactly one place.
        """
        return self.blc.resolve_leads(self.cfg, [p.overrides() for p in self.pages()])

    # -- actions -----------------------------------------------------------
    def set_banner(self, level, text):
        fg, bg = BANNER.get(level, ("#333333", "#e0e0e0"))
        self.banner.setText(text)
        self.banner.setStyleSheet(
            "background: %s; color: %s; border-radius: 3px; font-weight: bold;"
            % (bg, fg))

    def check(self):
        """Run the validation and show it. See the docstring on why this blocks."""
        try:
            leads = self.resolve()
        except Exception as exc:
            self.set_banner("FAIL", "Cannot build that set")
            self.detail.setPlainText(str(exc))
            return

        QtWidgets.QApplication.setOverrideCursor(QtCore.Qt.WaitCursor)
        self.status.setText("Measuring…")
        QtWidgets.QApplication.processEvents()
        try:
            if self.meshes is None:
                self.meshes = self.blc.load_meshes()
            corridor = json.load(open(self.blc.DEFAULT_CORRIDOR))
            foramen = (self.blc.load_foramen_corridors()
                       if any(l["type"] == "drg" for l in leads) else None)
            self.leads = leads
            self.outcome = self.blc.validate_set(leads, meshes=self.meshes,
                                                 corridor=corridor, foramen=foramen)
            lines = self.blc.report_set_lines("this set", leads, self.outcome)
            self.detail.setPlainText("\n".join(lines[1:]))

            levels = [lvl for r in self.outcome["leads"]
                      for lvl, _t, _m in r["checks"]]
            levels += [lvl for lvl, _t, _m in self.outcome["checks"]]
            worst = worst_of(levels)
            headline = {"PASS": "FITS", "WARN": "FITS, with a caveat",
                        "FAIL": "DOES NOT FIT"}[worst]
            if len(leads) > 1 and self.outcome["pairs"]:
                closest = min(p["gap_mm"] for p in self.outcome["pairs"])
                headline += "   —   %d leads, closest approach %.2f mm" \
                    % (len(leads), closest)
            elif self.outcome["leads"] and "clearance_mm" in self.outcome["leads"][0]["numbers"]:
                n = self.outcome["leads"][0]["numbers"]
                headline += "   —   %.2f mm widest contact, %+.2f mm clearance" \
                    % (n["widest_lead_mm"], n["clearance_mm"])
            self.set_banner(worst, headline)
            self.status.setText("")
            # Check fit doubles as "rebuild what is in the tree": if the leads
            # are showing, they are now the numbers that were just measured.
            if self.btn_preview.isChecked():
                self.do_preview()
            self.sync_preview_button()
        except Exception:
            self.outcome = None
            self.set_banner("FAIL", "The check itself failed")
            self.detail.setPlainText(traceback.format_exc())
            self.status.setText("")
        finally:
            QtWidgets.QApplication.restoreOverrideCursor()

    def need_outcome(self):
        """Showing and exporting both work off a checked set; check if needed."""
        if self.outcome is None:
            self.check()
        return self.outcome

    # -- the leads are either in the document or they are not -------------
    def toggle_style(self):
        """Stylesheet for the Show-leads toggle: green when checked.

        Both states are painted explicitly, and the unchecked one is painted
        from the widget's OWN palette rather than from named colours. That is
        what makes it theme-proof: FreeCAD ships light and dark stylesheets and
        several third-party ones, and a rule that only styled :checked would
        make Qt draw the whole button through the stylesheet engine -- leaving
        the normal state a flat rectangle with whatever text colour the theme
        happened to set for a NATIVE button, which on the dark themes is nearly
        invisible. Asking the palette means the off state matches the buttons
        beside it whatever the theme is, and the on state is a green that has
        enough contrast for white text either way.
        """
        pal = self.palette()
        face = pal.color(QtGui.QPalette.Button).name()
        text = pal.color(QtGui.QPalette.ButtonText).name()
        edge = pal.color(QtGui.QPalette.Mid).name()
        lit = pal.color(QtGui.QPalette.Midlight).name()
        off = pal.color(QtGui.QPalette.Dark).name()
        return ("""
            QPushButton {
                background: %s; color: %s;
                border: 1px solid %s; border-radius: 3px; padding: 4px 10px;
            }
            QPushButton:hover  { background: %s; }
            QPushButton:disabled { color: %s; }
            QPushButton:checked {
                background: %s; color: %s;
                border: 1px solid %s; font-weight: bold;
            }
            QPushButton:checked:hover { background: %s; }
        """ % (face, text, edge, lit, off,
               TOGGLE_ON_BG, TOGGLE_ON_FG, TOGGLE_ON_BORDER, TOGGLE_ON_HOVER))

    def preview_shown(self):
        """True if the leads group is actually in the active document."""
        doc = FreeCAD.ActiveDocument
        return doc is not None and doc.getObject(self.blc.PREVIEW_GROUP) is not None

    def sync_preview_button(self):
        """Make the toggle say what the DOCUMENT says, not what it last did.

        The group can go without the panel being told -- deleted in the tree,
        another document activated, the document closed -- and a button stuck in
        the green state would then be a lie. Checked without firing the toggle
        handler, or syncing would itself build or delete leads.
        """
        shown = self.preview_shown()
        if self.btn_preview.isChecked() != shown:
            self.btn_preview.blockSignals(True)
            self.btn_preview.setChecked(shown)
            self.btn_preview.blockSignals(False)
        self.btn_preview.setText("Leads shown" if shown else "Show leads")

    def preview_toggled(self, on):
        """The one handler for both directions."""
        if on:
            if not self.do_preview():
                # Nothing went into the document, so the button must not claim
                # otherwise. blockSignals so this does not re-enter as a clear.
                self.btn_preview.blockSignals(True)
                self.btn_preview.setChecked(False)
                self.btn_preview.blockSignals(False)
        else:
            self.do_clear()
        self.sync_preview_button()

    def do_preview(self):
        """Build the set into the active document. True if anything landed."""
        doc = FreeCAD.ActiveDocument
        if doc is None:
            self.status.setText("No active document to put the leads in.")
            return False
        outcome = self.need_outcome()
        if outcome is None or not any(self.blc.is_built(r) for r in outcome["leads"]):
            self.status.setText("Nothing to show: no lead could be built.")
            return False
        # A failing set is still shown, on purpose -- SEEING the lead push
        # through the dura, or the two leads sitting inside each other, is the
        # clearest possible explanation of the failure.
        try:
            group, made = self.blc.preview_set(doc, self.leads, outcome["leads"],
                                               self.blc.lead_colours())
        except Exception as exc:
            self.status.setText("Could not show the leads: %s" % exc)
            return False
        FreeCADGui.updateGui()
        self.status.setText(
            "%d bodies from %d lead(s) in %s, under “%s”. Disposable — do not "
            "save the document for them."
            % (len(made), len(self.leads), doc.Label, group.Label))
        return True

    def do_clear(self):
        doc = FreeCAD.ActiveDocument
        if doc is None:
            self.status.setText("No active document.")
            return
        n = self.blc.clear_preview(doc)
        FreeCADGui.updateGui()
        self.status.setText("Took %d object(s) back out of the tree." % n if n
                            else "There were no leads in the tree to remove.")

    def do_export(self):
        outcome = self.need_outcome()
        if outcome is None or not all(self.blc.is_built(r) for r in outcome["leads"]):
            self.status.setText("Nothing to export: a lead could not be built.")
            return
        if not outcome["ok"]:
            QtWidgets.QMessageBox.warning(
                self, "Lead designer",
                "This set does not fit, so it has not been exported."
                "\n\nThe fix is a different lead, a different position, or more "
                "space between two leads — the anatomy is not carved away to "
                "make room. See the reasons in the panel.")
            return
        # The name is asked for every time, because there is no catalogue to
        # take one from: it is a DIRECTORY name and nothing reads it back.
        name, ok = QtWidgets.QInputDialog.getText(
            self, "Export STLs",
            "Folder to write these %d lead(s) into, under generated_leads/:"
            % len(self.leads), text=self.suggested_name())
        if not ok or not name.strip():
            return
        name = name.strip()
        try:
            outdir, files = self.blc.export_set(name, self.leads, outcome["leads"])
        except Exception as exc:
            self.status.setText("Export failed: %s" % exc)
            return
        self.status.setText("Wrote %d files to %s" % (len(files), outdir))
        QtWidgets.QMessageBox.information(
            self, "Lead designer",
            "Wrote %d STLs from %d lead(s) to\n\n%s\n\nThat directory is the "
            "durable artefact — not a saved document, and not an entry in any "
            "list. Close the model document without saving."
            % (len(files), len(self.leads), outdir))

    def suggested_name(self):
        """A directory name derived from the leads themselves, to be edited.

        Built from what the set IS -- "dorsal_T11_x1.5", "2x_dorsal", "drg_L3" --
        so the offered name is never stale and nobody has to invent one. It is a
        suggestion in an editable box, not an identifier: nothing resolves it.
        """
        if not self.pages():
            return "lead"
        if len(self.pages()) > 1:
            counts = {}
            for page in self.pages():
                counts[page.kind] = counts.get(page.kind, 0) + 1
            return "_".join("%dx_%s" % (n, k) for k, n in sorted(counts.items()))
        page = self.pages()[0]
        if page.kind == "drg":
            # No contact count in the name: every DRG lead is the same
            # four-contact hardware, so the ganglion is the only thing that
            # distinguishes one from another.
            return "drg_%s_rado" % page.target.currentText()
        where = page.level.currentText()
        if where == CUSTOM:
            where = "z%.0f" % page.z_center.value()
        dx = page.x_offset.value()
        side = "" if abs(dx) < 0.005 else ("_L%.1f" % dx if dx > 0 else "_R%.1f" % -dx)
        return "%s_%s%s_%dc" % (page.kind, where, side, page.contacts.value())


def show_panel():
    mw = FreeCADGui.getMainWindow()
    try:
        blc = load_builder()
    except Exception as exc:
        QtWidgets.QMessageBox.critical(
            mw, "Lead designer",
            "Could not import build_lead_config.\n\n%s: %s\n\nLooked for the repo "
            "at:\n%s\n\nSet SCS_MODELING_REPO if the checkout lives somewhere else."
            % (type(exc).__name__, exc, REPO))
        return None
    try:
        panel = LeadDesigner(blc)
    except Exception:
        QtWidgets.QMessageBox.critical(mw, "Lead designer",
                                       "Could not build the panel.\n\n%s"
                                       % traceback.format_exc())
        return None

    dock = mw.findChild(QtWidgets.QDockWidget, OBJECT_NAME)
    if dock is None:
        dock = QtWidgets.QDockWidget("Lead designer", mw)
        dock.setObjectName(OBJECT_NAME)
        mw.addDockWidget(QtCore.Qt.RightDockWidgetArea, dock)
    dock.setWidget(panel)
    dock.show()
    dock.raise_()
    return dock


show_panel()
