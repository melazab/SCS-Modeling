"""Solve and display the field on a completed SCS Mesh Generator mesh.

Mesh settings come from the open mesh dock, or its last generated settings.
The visualizer requires a verified mesh for the live lead. It solves per-contact
basis fields once per model/background configuration; montage changes only
combine those fields. A cluster solve keeps its solution there and plots from
each contact's potential at the drawn surfaces (surface_basis.py). It does not
generate meshes or save the CAD document.
"""
import json
import os
import sys

import FreeCAD
import FreeCADGui

try:
    from PySide import QtCore, QtGui, QtWidgets
except ImportError:                                     # pragma: no cover
    try:
        from PySide6 import QtCore, QtGui, QtWidgets
    except ImportError:
        from PySide2 import QtCore, QtGui, QtWidgets

# Fixed, not derived from __file__: this macro is meant to be copied or
# symlinked into FreeCAD's Macro directory to appear in the Macro menu, and
# __file__ then points THERE, not at fem/scripts/ -- confirmed to actually
# break this way for a sibling macro once copied. A symlink wouldn't dodge
# it either: os.path.abspath() doesn't resolve symlinks. NEVER hard-link
# this file into the Macro directory -- always a symlink (`ln -s`).
REPO_ROOT = "/home/mohamed/Projects/SCS-Modeling"
FEM_SCRIPTS_DIR = os.path.join(REPO_ROOT, "fem", "scripts")
sys.path.insert(0, FEM_SCRIPTS_DIR)
import async_runner
import build_mesh
import config as C
import live_lead
import artifacts
import scs_job_service
import scs_field_display
import scs_montage as M
import scs_montage_feature as F
import scs_document_cache
import scs_waveform as W
import scs_fast_viewer
import scs_stages
import scs_monitor          # one sampler per session; never reloaded (it owns a poll timer)
from solve_cpu_limit import physical_core_limit
sys.path.insert(0, os.path.join(REPO_ROOT, "src", "freecad"))
import scs_ui

# Reloaded on every run -- same reason src/freecad/lead_designer.FCMacro's
# own load_builder() reloads build_lead_config, and the same reason
# SCS_Mesh_Generator.FCMacro does: FreeCAD keeps these modules in
# sys.modules across macro re-runs, so editing config.py/scs_montage.py/
# scs_montage_feature.py/live_lead.py and re-running this macro would
# otherwise keep running the OLD code with no error.
import importlib
for _m in (C, artifacts, M, F, live_lead, build_mesh, async_runner, scs_stages, scs_ui):
    try:
        importlib.reload(_m)
    except Exception:
        pass

FEM_VENV_PY = os.path.join(REPO_ROOT, "fem", ".venv", "bin", "python")
SOLVE_LEAD_SCRIPT = os.path.join(FEM_SCRIPTS_DIR, "solve_lead.py")

PREFERRED_DOC = "NBF_RADO_SCS"

GROUP_NAME = "SCS_PotentialFieldViz"
MONTAGE_NAME = "SCS_Montage"
OBJECT_NAME = "SCS_PotentialVisualizerDock"    # QDockWidget identity, so re-running finds it
MESH_GENERATOR_DOCK_NAME = "SCS_MeshGeneratorDock"
PIPE_LABELS = {
    "epidural": ("SCS_Epidural_PotentialField", "Epidural space -- SCS potential field"),
    "dura": ("SCS_Dura_PotentialField", "Dura -- SCS potential field"),
    "csf": ("SCS_CSF_PotentialField", "CSF -- SCS potential field"),
    "white": ("SCS_White_PotentialField", "White matter -- SCS potential field"),
    "grey": ("SCS_Grey_PotentialField", "Grey matter -- SCS potential field"),
}

PIPE_LABELS.update({t: (F.PIPE_NAMES[t], M.TISSUE_LABELS[t] + " -- SCS potential field")
                    for t in M.TISSUES if t not in PIPE_LABELS})

LIVE_LEAD_POLL_MS = 1500
THREAD_ENV_VARS = ("OMP_NUM_THREADS", "OPENBLAS_NUM_THREADS", "MKL_NUM_THREADS",
                   "NUMEXPR_NUM_THREADS", "VECLIB_MAXIMUM_THREADS")

# Combined-progress weighting for the self-sufficient "Plot Field" chain:
# meshing is the slower of the two stages by roughly this ratio (measured
# field-of-record default-parameter timings: ~740s mesh vs ~300s solve --
# see SCS_Mesh_Generator.FCMacro's own module docstring), so it gets 70% of
# the combined bar and solving gets the remaining 30%. Not claimed to be
# perfectly calibrated -- monotonic and not wildly misleading is the bar
# Mohamed's brief actually sets.


def get_target_document():
    if FreeCAD.ActiveDocument is not None:
        return FreeCAD.ActiveDocument
    if PREFERRED_DOC in FreeCAD.listDocuments():
        return FreeCAD.getDocument(PREFERRED_DOC)
    if FreeCAD.ActiveDocument is not None:
        print(
            "'%s' not open; using active document '%s' instead"
            % (PREFERRED_DOC, FreeCAD.ActiveDocument.Name)
        )
        return FreeCAD.ActiveDocument
    print("no document open; creating a new one")
    return FreeCAD.newDocument("SCSPotentialViz")


def read_shared_mesh_params():
    """SCS_Mesh_Generator.FCMacro's dock's CURRENT size-field values, if
    that dock happens to be open in this same FreeCAD session -- both
    macros run in the same process, so its panel object is just sitting on
    the Qt object tree, no IPC needed. Falls back to
    build_mesh.DEFAULT_PARAMS (Mohamed's own brief: "if not, reading
    build_mesh.DEFAULT_PARAMS as the fallback is fine") if that dock isn't
    open, or is open but not (yet) the expected panel type."""
    mw = FreeCADGui.getMainWindow()
    dock = mw.findChild(QtWidgets.QDockWidget, MESH_GENERATOR_DOCK_NAME)
    if dock is not None:
        panel = dock.widget()
        if panel is not None and hasattr(panel, "mesh_params") and panel.doc == FreeCAD.ActiveDocument:
            try:
                return panel.mesh_params()
            except Exception as exc:
                print("SCS Potential Visualizer: could not read Mesh Generator's "
                      "current parameters (%s) -- falling back to "
                      "build_mesh.DEFAULT_PARAMS" % exc)
    try:
        saved = scs_document_cache.document_params(FreeCAD.ActiveDocument)
        if saved is not None:
            return saved
        with open(os.path.join(C.OUT, 'mesh_settings.json')) as fh:
            return json.load(fh)
    except (OSError, ValueError):
        return dict(build_mesh.DEFAULT_PARAMS)


def get_or_create(doc, name, type_id, parent=None):
    obj = doc.getObject(name)
    created = False
    if obj is None:
        obj = doc.addObject(type_id, name)
        created = True
        if parent is not None:
            parent.addObject(obj)
    return obj, created


def apply_field_with_stale_range_fix(pipe, field_name):
    """Setting ViewObject.Field once, immediately after a pipeline's data
    first exists, captures FreeCAD's colour-bar range before the pipeline
    has really finished -- it sticks at the -0.5/+0.5 default and never
    updates again even though pipe.Data is correct. Found and fixed
    2026-09-11 in view_elmer_result.FCMacro; same fix, same reason, here."""
    doc = pipe.Document
    enum = pipe.ViewObject.getEnumerationsOfProperty("Field")
    if field_name not in enum:
        print("WARNING: '%s' not in Field enum for %s -- got %s" % (field_name, pipe.Name, enum))
        return False
    pipe.ViewObject.Field = "None"
    doc.recompute([pipe])
    pipe.ViewObject.Field = field_name
    doc.recompute([pipe])
    return True


def load_pipe(pipe, vtp_path, clamp_v):
    """(Re)load one tissue pipeline from a freshly written .vtp. Shared by
    the initial bootstrap and by the panel's Plot Field action, so there is
    exactly one place doing the DisplayMode/Field dance."""
    doc = pipe.Document
    pipe.read(vtp_path)
    pipe.ViewObject.DisplayMode = "Surface"
    doc.recompute([pipe])
    # NOT FreeCADGui.updateGui() -- see module docstring.
    pipe.ViewObject.DisplayMode = "Wireframe"
    doc.recompute([pipe])
    pipe.ViewObject.DisplayMode = "Surface"
    doc.recompute([pipe])
    field_name = "V_clamped_%gV" % clamp_v
    applied = apply_field_with_stale_range_fix(pipe, field_name)
    if not applied:
        apply_field_with_stale_range_fix(pipe, "V_volts")
    pipe.ViewObject.Visibility = True


def ensure_pipes(doc):
    """Create (or find) the group, the five tissue pipelines and
    SCS_Montage. Does NOT load any data or run the montage -- that only
    happens once Plot Field is pressed and a solved field is available.
    Rebuilds SCS_Montage if it predates the SolutionNpz property. Returns
    (group, {tissue: pipe}, montage_obj)."""
    grp, _ = get_or_create(doc, GROUP_NAME, "App::DocumentObjectGroup")
    grp.Label = "SCS potential field (interactive montage)"

    labels = dict(PIPE_LABELS)
    info = live_lead.find_live_lead(doc)
    if info['status'] == live_lead.LiveLeadStatus.OK:
        for index in info['contacts']:
            key = 'contact_%d' % index
            labels[key] = ('SCS_%s_PotentialField' % key,
                          live_lead.contact_label(info, index) + ' -- SCS potential field')
        for lead in info['lead_indices']:
            key = 'insulator_%d' % lead
            labels[key] = ('SCS_%s_PotentialField' % key, 'Lead %d insulation -- SCS potential field' % lead)
        # Upgrade older completed meshes with display-only insulation exports.
        import scs_document_cache
        run = scs_document_cache.document_run(doc)
        if run:
            arrays = live_lead.tessellate_lead_arrays(info)
            if scs_document_cache.geometry_matches(arrays, run):
                live_lead.write_insulator_surfaces(arrays, os.path.join(run, 'lead'))
    pipes = {}
    for tissue, (pipe_name, label) in labels.items():
        pipe, created = get_or_create(doc, pipe_name, "Fem::FemPostPipeline", grp)
        pipe.Label = label
        if created:
            pipe.ViewObject.Visibility = False
        pipes[tissue] = pipe

    montage_obj = doc.getObject(MONTAGE_NAME)
    if montage_obj is not None and "SolutionNpz" not in montage_obj.PropertiesList:
        doc.removeObject(montage_obj.Name)
        montage_obj = None
    if montage_obj is None:
        montage_obj = doc.addObject("App::FeaturePython", MONTAGE_NAME)
        F.SCSMontageProxy(montage_obj)
        if FreeCAD.GuiUp:
            F.SCSMontageViewProxy(montage_obj.ViewObject)
        grp.addObject(montage_obj)
    else:
        # Reloading a module does not update instances already in a document.
        # Replace their callbacks without recreating properties/current values.
        # Clear first: attaching a ViewProvider can immediately call updateData.
        montage_obj.Proxy = F.SCSMontageProxy.__new__(F.SCSMontageProxy)
        if FreeCAD.GuiUp:
            F.SCSMontageViewProxy(montage_obj.ViewObject)

    if 'IncludeBackground' not in montage_obj.PropertiesList:
        montage_obj.addProperty('App::PropertyBool', 'IncludeBackground', 'Solve settings',
            'Include unclassified mesh volume as conductive background on the next solve.')
        montage_obj.IncludeBackground = montage_obj.SolutionNpz.endswith('solution_bg.npz')
    F.SCSMontageProxy.ensure_revision(montage_obj)
    scs_field_display.ensure_setting(montage_obj)
    scs_field_display.apply(doc)

    if info['status'] == live_lead.LiveLeadStatus.OK:
        F.group_lead_pipes(doc, info['contact_map'])
        old_insulation = doc.getObject('SCS_insulator_PotentialField')
        if old_insulation is not None:
            if not montage_obj.SolutionNpz:
                doc.removeObject(old_insulation.Name)
            else:
                old_insulation.ViewObject.Visibility = False
                old_insulation.Label = 'Combined insulation (legacy preview)'
    return grp, pipes, montage_obj


def role_of(value):
    if value > 0:
        return "source/anode"
    if value < 0:
        return "sink/cathode"
    return "floating"


ROLE_STYLES = {
    "source/anode":  "color: #1b5e20; font-weight: bold;",
    "sink/cathode":  "color: #8e0000; font-weight: bold;",
    "floating":      "color: gray;",
}


class PotentialVisualizerPanel(QtWidgets.QWidget):
    """Live-lead status, one current per contact, one Solve / Plot button for
    the matching mesh, its stages and a short readout -- laid out like SCS Mesh
    Generator."""

    def __init__(self, doc):
        super(PotentialVisualizerPanel, self).__init__()
        self.doc = doc
        _grp, self.pipes, self.montage_obj = ensure_pipes(doc)
        if not self.montage_obj.SolutionNpz:
            # Recover older panels that erased the binding, using only the
            # current geometry/mesh run's last completed, verified solve.
            _info, run_dir = self.resolve_run()
            if run_dir:
                try:
                    with open(os.path.join(run_dir, 'solve_report.json')) as fh:
                        background = json.load(fh)['background_included']
                    if live_lead.field_ready(run_dir, background):
                        self.montage_obj.SolutionNpz = os.path.join(
                            run_dir, 'solution_bg.npz' if background else 'solution.npz')
                except (OSError, ValueError, KeyError):
                    pass
        W.ensure_properties(self.montage_obj)
        # Field surfaces are never picked under the mouse: dense surfaces make
        # every mouse move slow. The tree selects them.
        scs_field_display.set_enabled(doc, False)
        self._current_sol_npz = self.montage_obj.SolutionNpz or None
        self._live_lead_info = dict(status=live_lead.LiveLeadStatus.NONE, reason="")
        self._pending_run_dir = None
        self._pending_live_dir = None
        self._aborting = False
        self._gate = None
        self._remote_note = ""

        self.solve_runner = async_runner.AsyncProcessRunner(
            self, FEM_VENV_PY, SOLVE_LEAD_SCRIPT, "SOLVE_JSON ")
        self.solve_runner.progress.connect(self.on_plot_solve_progress)
        self.solve_runner.stage_message.connect(self.on_solve_stage)
        self.solve_runner.tick.connect(self.on_solve_tick)
        self.solve_runner.finished_ok.connect(self.on_plot_solve_finished)
        self.solve_runner.failed.connect(self.on_plot_failed)
        self.solve_runner.aborted.connect(self.on_plot_aborted)

        root_layout = QtWidgets.QVBoxLayout(self)
        root_layout.setContentsMargins(0, 0, 0, 0)
        scroll = QtWidgets.QScrollArea()
        scroll.setWidgetResizable(True)
        content = QtWidgets.QWidget()
        scroll.setWidget(content)
        root_layout.addWidget(scroll)
        outer = QtWidgets.QVBoxLayout(content)
        outer.setContentsMargins(6, 6, 6, 6)
        outer.setSpacing(6)

        self.lead_status = QtWidgets.QLabel("")
        self.lead_status.setAlignment(QtCore.Qt.AlignCenter)
        self.lead_status.setMinimumHeight(24)
        self.lead_status.setWordWrap(True)
        self.lead_status.setToolTip(
            "Leads in this document's tree (placed by Lead Designer), rechecked every %.1f s."
            % (LIVE_LEAD_POLL_MS / 1000.0))
        outer.addWidget(self.lead_status)

        # -- the solve: one field per contact (1 A each), so it needs no currents.
        # Where it runs, and whether the volume outside the anatomy conducts.
        run_row = QtWidgets.QHBoxLayout()
        run_row.addWidget(QtWidgets.QLabel("Run on"))
        store = scs_job_service.service().store
        self._profile_keys = sorted(store.profiles, key=lambda k: (store.profiles[k]["backend"] != "local", k))
        self.run_on = scs_ui.Segmented([store.profiles[k]["name"].replace(" workstation", "")
                                        for k in self._profile_keys])
        self.run_on.changed.connect(self.on_run_on)
        run_row.addWidget(self.run_on, 1)
        manager = QtWidgets.QToolButton()
        manager.setText("⚙")
        manager.setToolTip("Job Manager: execution settings (CPUs, memory, partition) and all jobs")
        manager.clicked.connect(lambda: __import__('scs_job_manager').show())
        run_row.addWidget(manager)
        outer.addLayout(run_row)

        self.background_check = QtWidgets.QCheckBox("Include background tissue")
        self.background_check.setChecked(self.montage_obj.IncludeBackground)
        self.background_check.setToolTip(
            "Solve the mesh volume outside the classified anatomy as conducting background "
            "(bone conductivity). A separate solve, cached separately.")
        self.background_check.toggled.connect(
            lambda checked: setattr(self.montage_obj, 'IncludeBackground', checked))
        self.background_check.toggled.connect(self.refresh_gates)
        outer.addWidget(self.background_check)
        self.btn_solve = QtWidgets.QPushButton("Solve")
        self.btn_solve.setMinimumHeight(30)
        self.btn_solve.setStyleSheet(scs_ui.action_style(self.btn_solve))
        self.btn_solve.clicked.connect(self.on_solve_button)
        outer.addWidget(self.btn_solve)
        self.stages = scs_stages.StageView("Solve")
        outer.addWidget(self.stages)

        # -- currents: any montage of the solved fields, plotted in seconds -----
        self.montage_group = QtWidgets.QGroupBox("Currents")
        mv = QtWidgets.QVBoxLayout(self.montage_group)
        # Rebuilt by _rebuild_contact_rows() to exactly the live lead's contacts.
        self.contact_form = QtWidgets.QFormLayout()
        self.contact_form.setLabelAlignment(QtCore.Qt.AlignRight)
        self.contact_spins = []
        self.role_labels = []
        self._current_n_contacts = 0
        contact_widget = QtWidgets.QWidget()
        contact_widget.setLayout(self.contact_form)
        contact_scroll = QtWidgets.QScrollArea()
        contact_scroll.setWidgetResizable(True)
        contact_scroll.setFrameShape(QtWidgets.QFrame.NoFrame)
        contact_scroll.setWidget(contact_widget)
        contact_scroll.setMinimumHeight(160)
        contact_scroll.setMaximumHeight(280)
        mv.addWidget(contact_scroll)
        current_row = QtWidgets.QHBoxLayout()
        self.total_current = QtWidgets.QDoubleSpinBox()
        self.total_current.setRange(.001, 5000.)
        self.total_current.setDecimals(3)
        self.total_current.setValue(sum(max(0., getattr(self.montage_obj, F.contact_prop_name(i))) for i in F.contact_indices(self.montage_obj)) or 2.4)
        self.total_current.setSuffix(' mA total')
        self.total_current.setToolTip('Total source current across all leads, with an equal return.')
        current_row.addWidget(self.total_current, 1)
        scale_button = QtWidgets.QPushButton('Scale to total')
        scale_button.setToolTip('Scale the contacts above to this total, keeping their ratios.')
        scale_button.clicked.connect(self.scale_to_total)
        current_row.addWidget(scale_button)
        mv.addLayout(current_row)
        self.total_label = QtWidgets.QLabel('')
        self.total_label.setStyleSheet('color: gray;')
        mv.addWidget(self.total_label)

        show_row = QtWidgets.QHBoxLayout()
        show_row.addWidget(QtWidgets.QLabel("Show"))
        self.show_quantity = scs_ui.Segmented(F.QUANTITIES, [
            "Potential, V", "Electric field magnitude |E|, V/m, inside each tissue (needs a field "
            "solved since 2026-10-23, or its surface basis rebuilt)"])
        self.show_quantity.set_index(F.QUANTITIES.index(self.montage_obj.PlotQuantity))
        self.show_quantity.changed.connect(self.on_quantity)
        show_row.addWidget(self.show_quantity, 1)
        mv.addLayout(show_row)
        form = QtWidgets.QFormLayout()
        form.setLabelAlignment(QtCore.Qt.AlignRight)
        self.clamp_spin = QtWidgets.QDoubleSpinBox()
        self.clamp_spin.setRange(0.0, 100000.0)
        self.clamp_spin.setSingleStep(10.0)
        self.clamp_spin.setDecimals(3)
        self.clamp_spin.setSuffix(" " + self.unit())
        self.clamp_spin.setSpecialValueText("auto")
        self.clamp_spin.setValue(self.montage_obj.ClampVolts)
        self.clamp_spin.setToolTip(
            "Colour scale saturates at +/- this voltage. auto: the 95th percentile of |V| "
            "over epidural space, dura, CSF and the cord, for this montage.")
        form.addRow("Colour range ±", self.clamp_spin)
        mv.addLayout(form)
        self.btn_plot = QtWidgets.QPushButton("Plot field")
        self.btn_plot.setMinimumHeight(30)
        self.btn_plot.setStyleSheet(scs_ui.action_style(self.btn_plot))
        self.btn_plot.setToolTip("Plot these currents on the solved field")
        self.btn_plot.clicked.connect(self.on_plot_button)
        mv.addWidget(self.btn_plot)
        outer.addWidget(self.montage_group)

        # -- what the plotted montage reads, once plotted -------------------
        self.readout = QtWidgets.QWidget()
        rg = QtWidgets.QGridLayout(self.readout)
        rg.setContentsMargins(0, 0, 0, 0)
        rg.setHorizontalSpacing(10)
        rg.setVerticalSpacing(1)
        self.plot_line = QtWidgets.QLabel("")
        rg.addWidget(self.plot_line, 0, 0, 1, 4)
        self.tissue_labels = {}
        for n, t in enumerate(M.TISSUES):
            name = QtWidgets.QLabel(M.TISSUE_LABELS.get(t, t))
            name.setStyleSheet("color: gray;")
            value = QtWidgets.QLabel("-")
            rg.addWidget(name, 1 + n//2, 2*(n % 2))
            rg.addWidget(value, 1 + n//2, 2*(n % 2) + 1)
            self.tissue_labels[t] = value
        self.readout.setToolTip("Voltage range on each tissue's surface for the plotted montage.")
        self.readout.setVisible(False)
        outer.addWidget(self.readout)

        # -- log and waveform, hidden until asked for -----------------------
        tools = QtWidgets.QHBoxLayout()
        self.log_toggle = QtWidgets.QToolButton()
        self.log_toggle.setText("Log")
        self.log_toggle.setCheckable(True)
        self.log_toggle.setToolTip("The solver's output")
        tools.addWidget(self.log_toggle)
        self.wave_toggle = QtWidgets.QToolButton()
        self.wave_toggle.setText("Waveform")
        self.wave_toggle.setCheckable(True)
        self.wave_toggle.setToolTip("Biphasic waveform snapshots and the shareable animation export")
        tools.addWidget(self.wave_toggle)
        tools.addStretch(1)
        outer.addLayout(tools)

        self.waveform = QtWidgets.QWidget()
        wf = QtWidgets.QFormLayout(self.waveform)
        wf.setContentsMargins(0, 0, 0, 0)
        wf.setLabelAlignment(QtCore.Qt.AlignRight)
        self.wave_mode = QtWidgets.QComboBox()
        self.wave_mode.addItems(['Static', 'FAST-style biphasic'])
        self.wave_mode.setCurrentText(str(self.montage_obj.WaveformMode))
        wf.addRow('Mode', self.wave_mode)
        self.wave_spins = {}
        for prop, label, low, high, suffix, tip in (
            ('FrequencyHz', 'Frequency', .01, 10000., ' Hz', ''),
            ('PhaseWidthUs', 'Width per phase', 1., 100000., ' µs', '220 µs is the usual comparison'),
            ('InterphaseGapUs', 'Gap', 0., 100000., ' µs', 'Assumed; 0 unless known')):
            spin = QtWidgets.QDoubleSpinBox()
            spin.setRange(low, high)
            spin.setDecimals(2)
            spin.setSuffix(suffix)
            spin.setValue(getattr(self.montage_obj, prop))
            spin.setToolTip(tip)
            self.wave_spins[prop] = spin
            wf.addRow(label, spin)
        self.phase_choice = QtWidgets.QComboBox()
        self.phase_choice.addItems(['First phase', 'Reverse phase', 'Interpulse interval'])
        self.phase_choice.currentIndexChanged.connect(lambda *_: self.apply_montage())
        wf.addRow('Snapshot', self.phase_choice)
        viewer = QtWidgets.QPushButton('Export animation…')
        viewer.setToolTip('A self-contained HTML viewer: playback and annotated PNGs of this montage')
        viewer.clicked.connect(self.export_fast_viewer)
        wf.addRow(viewer)
        self.waveform.setVisible(False)
        self.wave_toggle.toggled.connect(self.waveform.setVisible)
        outer.addWidget(self.waveform)

        self.solve_detail = QtWidgets.QPlainTextEdit()
        self.solve_detail.setReadOnly(True)
        self.solve_detail.document().setMaximumBlockCount(200)
        self.solve_detail.setMaximumHeight(160)
        self.solve_detail.setVisible(False)
        self.log_toggle.toggled.connect(self.solve_detail.setVisible)
        outer.addWidget(self.solve_detail)
        outer.addStretch(1)

        self._poll_timer = QtCore.QTimer(self)
        self._poll_timer.timeout.connect(lambda: self.refresh_gates() if self.isVisible() else None)
        self._poll_timer.start(LIVE_LEAD_POLL_MS)
        self.refresh_gates()

    # -- live lead / gating ----------------------------------------------
    def busy(self):
        return self.solve_runner.is_running()

    def resolve_run(self):
        """(lead_info, run_dir) for the CURRENT live lead + the CURRENT
        shared/default mesh params -- same pattern as
        SCS_Mesh_Generator.FCMacro.resolve_run(), duplicated rather than
        imported because it is five lines of pure orchestration over
        live_lead.py's shared functions, not physics or caching logic
        itself (which DOES live in one place, live_lead.py)."""
        info = live_lead.find_live_lead(self.doc)
        self._live_lead_info = info
        if info["status"] != live_lead.LiveLeadStatus.OK:
            return info, None
        arrays = live_lead.tessellate_lead_arrays(info)
        run_dir = scs_document_cache.resolve_run(self.doc, arrays, read_shared_mesh_params())
        return info, run_dir

    def on_run_on(self, i):
        """The Run on switch: this document's execution profile."""
        try:
            scs_job_service.service().select_profile(self.doc, self._profile_keys[i])
        except ValueError as exc:
            self.stages.idle(str(exc))
        self.refresh_gates()

    def solve_summary(self, run_dir, background):
        """One line for a solved field: contacts, worst residual, peak memory,
        time, and where the solution itself is."""
        report = live_lead.load_report(run_dir, "solve_report") if run_dir else None
        if not report:
            return "Solved field"
        res = report.get("relative_residuals") or []
        bits = ["%d contacts" % len(res) if res else "solved",
                ("residual ≤ %.0e" % max(res)) if res else "",
                ("peak %.0f GB" % report["peak_rss_gb"]) if report.get("peak_rss_gb") else "",
                scs_stages.duration(report["elapsed_s"]) if report.get("elapsed_s") else ""]
        name = 'solution_bg.npz' if background else 'solution.npz'
        if not os.path.isfile(os.path.join(run_dir, name)):
            kept = live_lead.kept_on_cluster(run_dir)
            size = kept.get('files', {}).get(name)
            bits.append("solution on %s%s" % (kept.get('host', 'the cluster'),
                                              (" (%.1f GB)" % (size/1e9)) if size else ""))
        return " · ".join(b for b in bits if b)

    def refresh_gates(self):
        busy = self.busy()
        try:
            profile = scs_job_service.service().profile(self.doc)
            self.run_on.setToolTip(
                ("%s: %s, sbatch %s" % (profile['name'], profile['host'], profile['sbatch_options']))
                if profile['backend'] == 'slurm' else
                ("%s: %d CPUs, %.0f GB" % (profile['name'], profile.get('solve_cpus', 0), profile.get('memory_gb', 0))))
        except ValueError as exc:
            self.run_on.setToolTip(str(exc))
        key = scs_job_service.service().profile_key(self.doc)
        if key in self._profile_keys:
            self.run_on.set_index(self._profile_keys.index(key))
        self.run_on.setEnabled(not busy)
        self.btn_solve.setStyleSheet(scs_ui.action_style(self.btn_solve, stop=busy))
        if busy:
            self.btn_solve.setText("Aborting…" if self._aborting else "Abort solve")
            self.btn_solve.setEnabled(not self._aborting)
            self.btn_plot.setEnabled(False)
            return  # don't fight the running solve's own stages
        self._aborting = False
        info, run_dir = self.resolve_run()
        if info["status"] == live_lead.LiveLeadStatus.OK:
            n = info["n_contacts"]
            if info['contact_map'] != getattr(self, '_contact_map', None):
                F.SCSMontageProxy.ensure_contact_mapping(self.montage_obj, info)
                self._contact_map = info['contact_map']
                self._rebuild_contact_rows(n)
            async_runner.set_status(self.lead_status, "active", live_lead.ready_text(info))
        elif info["status"] == live_lead.LiveLeadStatus.NONE:
            async_runner.set_status(self.lead_status, "idle", info["reason"])
        else:
            async_runner.set_status(self.lead_status, "gated", info["reason"])

        background = self.background_check.isChecked()
        if self._current_sol_npz is not None:
            expected = os.path.join(run_dir, 'solution_bg.npz' if background else 'solution.npz') if run_dir else None
            if expected != self._current_sol_npz or not live_lead.field_ready(run_dir, background):
                self._current_sol_npz = None
                self.montage_obj.SolutionNpz = ''
                for pipe in self.pipes.values():
                    pipe.ViewObject.Visibility = False
                self.readout.setVisible(False)
                self._gate = None
        valid_lead = run_dir is not None
        self.montage_group.setEnabled(valid_lead)
        mesh = valid_lead and live_lead.mesh_ready(run_dir)
        field = mesh and live_lead.field_ready(run_dir, background)
        self.btn_solve.setText("Solved" if field else "Solve")
        self.btn_solve.setEnabled(mesh and not field)
        self.btn_solve.setToolTip(
            "This mesh is solved; plot any currents below" if field else
            "One field per contact (1 A each) for this mesh; any currents are then a quick plot" if mesh else
            "Mesh this lead first (SCS Mesh Generator)" if valid_lead else info["reason"])
        self.btn_plot.setEnabled(field)
        sol = os.path.join(run_dir, 'solution_bg.npz' if background else 'solution.npz') if field else None
        has_e = bool(sol) and M.has_E(sol)
        self.show_quantity.group.button(1).setEnabled(has_e)
        if not has_e and self.show_quantity.index() == 1:
            self.show_quantity.set_index(0)
            self.on_quantity(0)
        # Only a change of state rewrites the caption, so a result or an error stays put.
        gate = "field" if field else "solve" if mesh else "mesh" if valid_lead else "lead"
        if gate != self._gate:
            self._gate = gate
            if gate == "field":
                self.stages.done(self.solve_summary(run_dir, background))
            elif gate == "mesh":
                self.stages.idle("Mesh this lead first (SCS Mesh Generator).")
            else:
                self.stages.idle("")

    def _rebuild_contact_rows(self, n_contacts):
        """Rebuild self.contact_form so it has EXACTLY n_contacts spinbox
        rows (Contact 1..n_contacts) -- called from refresh_gates()
        whenever the live lead's own contact count changes, including the
        very first time a lead is found (from 0). Also keeps the
        SCS_Montage document object's own Contact<i>_mA properties in sync
        via F.SCSMontageProxy.ensure_contact_properties(), so the Data tab
        and this dock's spinboxes never disagree about how many contacts
        exist. Per Mohamed's brief, a new row starts at 0 mA/floating --
        nothing is pre-assigned a role -- and an existing row for a
        contact number that's KEPT (e.g. going from 6 contacts to 4 keeps
        rows 1-4) is not touched here since it isn't rebuilt."""
        while self.contact_form.rowCount():
            self.contact_form.removeRow(0)
        self.contact_spins = []
        self.role_labels = []
        for i in range(1, n_contacts + 1):
            row = QtWidgets.QWidget()
            row_h = QtWidgets.QHBoxLayout(row)
            row_h.setContentsMargins(0, 0, 0, 0)
            spin = QtWidgets.QDoubleSpinBox()
            spin.setRange(-5000.0, 5000.0)
            spin.setSingleStep(0.1)
            spin.setDecimals(3)
            spin.setSuffix(" mA")
            spin.setValue(float(getattr(self.montage_obj, 'Contact%d_mA' % i, 0.0)))
            spin.setToolTip("Current into contact %d: + source (anode), − sink (cathode), 0 floating." % i)
            role_lbl = QtWidgets.QLabel(role_of(spin.value()))
            role_lbl.setStyleSheet(ROLE_STYLES[role_of(spin.value())])
            role_lbl.setMinimumWidth(56)
            spin.valueChanged.connect(lambda v, lbl=role_lbl: self.update_role(lbl, v))
            spin.valueChanged.connect(self.update_totals)
            self.contact_spins.append(spin)
            self.role_labels.append(role_lbl)
            row_h.addWidget(spin, 1)
            row_h.addWidget(role_lbl)
            self.contact_form.addRow(live_lead.contact_label(self._live_lead_info, i), row)
        self._current_n_contacts = n_contacts
        F.SCSMontageProxy.ensure_contact_properties(self.montage_obj, n_contacts)
        self.update_totals()

    def update_totals(self, *_):
        source, sink = W.totals([spin.value() for spin in self.contact_spins])
        self.total_label.setText('source %.4g · sink %.4g mA' % (abs(source), abs(sink)))

    def scale_to_total(self):
        try:
            values = W.normalize([s.value() for s in self.contact_spins], self.total_current.value())
            for spin, value in zip(self.contact_spins, values):
                spin.setValue(value)
            # Correct rounding at the final contact of each polarity.
            for sign in (1, -1):
                active = [s for s in self.contact_spins if s.value()*sign > 0]
                residual = sign*self.total_current.value()-sum(s.value() for s in active)
                active[-1].setValue(active[-1].value()+residual)
            self.update_totals()
        except ValueError as exc:
            self.total_label.setText(str(exc))

    def sync_waveform(self):
        obj = self.montage_obj
        obj.WaveformMode = self.wave_mode.currentText()
        for prop, spin in self.wave_spins.items():
            setattr(obj, prop, spin.value())
        period = W.validate(obj.FrequencyHz, obj.PhaseWidthUs, obj.InterphaseGapUs)
        w, g = obj.PhaseWidthUs/1000., obj.InterphaseGapUs/1000.
        obj.WaveformTimeMs = [w/2, w+g+w/2, (2*w+g+period)/2][self.phase_choice.currentIndex()]
        if obj.WaveformMode != 'Static':
            W.require_balanced([s.value() for s in self.contact_spins])

    def export_fast_viewer(self):
        if self.busy() or not self.montage_obj.SolutionNpz:
            self.stages.set_caption('Plot a field first.')
            return
        path, _ = QtWidgets.QFileDialog.getSaveFileName(self, 'Export shareable FAST viewer',
                          os.path.join(REPO_ROOT, self.doc.Name+'_FAST.html'), 'HTML (*.html)')
        if not path:
            return
        try:
            self.sync_waveform()
            self.montage_obj.Proxy.validate_binding(self.montage_obj)
            currents = [s.value() for s in self.contact_spins]
            total = W.require_balanced(currents)
            solution = self.montage_obj.SolutionNpz
            clamp = self.clamp_spin.value() or M.choose_clamp_v(currents, sol_npz=solution)
            surfaces = {name: M.sample_tissue(name, currents, sol_npz=solution, surface_path=surface)
                        for name, surface in M.surface_paths(solution).items()}
            visible = []
            for name in surfaces:
                pipe = self.doc.getObject(F.PIPE_NAMES.get(name, 'SCS_%s_PotentialField' % name))
                if pipe is not None and pipe.ViewObject.Visibility:
                    visible.append(name)
            metadata = dict(title=self.doc.Label, frequency_hz=self.montage_obj.FrequencyHz,
                width_us=self.montage_obj.PhaseWidthUs, gap_us=self.montage_obj.InterphaseGapUs,
                gap_is_assumed=True, currents_mA=currents, total_mA=total, clamp_v=clamp,
                contact_map=self._contact_map, solution=solution, visible=visible,
                electrical_model='Linear resistive; phase two reverses all contact currents',
                references=['Metzger et al. 2021, doi:10.1080/17434440.2021.1890580',
                            'Van Acker and Kim 2023, doi:10.1097/PHM.0000000000002268'])
            if not path.lower().endswith('.html'):
                path += '.html'
            scs_fast_viewer.export(path, surfaces, metadata)
            self.stages.set_caption('Exported ' + path)
        except Exception as exc:
            self.stages.set_caption('Export failed: ' + str(exc), scs_stages.FAIL_FG)

    def unit(self):
        return "V/m" if self.montage_obj.PlotQuantity == F.QUANTITIES[1] else "V"

    def on_quantity(self, i):
        """Potential or |E|: the colour range starts over (volts are not V/m),
        and a plotted montage is redrawn as the other quantity."""
        self.montage_obj.PlotQuantity = F.QUANTITIES[i]
        self.clamp_spin.setValue(0.0)
        self.clamp_spin.setSuffix(" " + self.unit())
        if self._current_sol_npz is not None and self.readout.isVisible():
            self.apply_montage()

    def update_role(self, label, value):
        role = role_of(value)
        label.setText(role)
        label.setStyleSheet(ROLE_STYLES[role])

    def env_overrides(self):
        # CPU allocation is passed explicitly to Elmer as MPI tasks. Python
        # preparation and each rank must not spawn another full pool of threads.
        return {v: 1 for v in THREAD_ENV_VARS}

    # -- Solve (or Abort) and Plot field ---------------------------------
    def on_solve_button(self):
        if self.busy():
            if not self._aborting:
                self._aborting = True
                self.refresh_gates()
                self.solve_runner.abort()
            return
        self.start_solve()

    def prepare_run(self):
        """The live lead's matching mesh run, with its lead surfaces written, or None."""
        try:
            scs_job_service.service().profile(self.doc)
        except ValueError as exc:
            self.stages.idle(str(exc))
            return None
        info, run_dir = self.resolve_run()
        if run_dir is None or not live_lead.mesh_ready(run_dir):
            self.refresh_gates()
            return None
        live_dir = os.path.join(run_dir, "lead")
        live_lead.write_insulator_surfaces(live_lead.tessellate_lead_arrays(info), live_dir)
        self._pending_run_dir = run_dir
        self._pending_background = self.background_check.isChecked()
        self._pending_live_dir = live_dir
        return run_dir

    def start_solve(self):
        run_dir = self.prepare_run()
        if run_dir is None:
            return
        background = self.background_check.isChecked()
        if live_lead.field_ready(run_dir, background):
            self.refresh_gates()
            return
        args = [run_dir, "--lead-dir", self._pending_live_dir]
        profile = scs_job_service.service().profile(self.doc)
        if profile['backend'] == 'local' and live_lead.mesh_remote_only(run_dir):
            self.on_plot_failed("This mesh is on the cluster: solve there, or fetch mesh.npz "
                                "with fem/hpc/fetch_run.sh.")
            return
        if profile['backend'] == 'local':
            settings = dict(cpus=profile['solve_cpus'], memory_gb=profile['memory_gb'])
            artifacts.atomic_json(os.path.join(C.OUT, 'solve_settings.json'), settings)
            args.extend(['--cpus', str(settings['cpus']), '--memory-gb', str(settings['memory_gb'])])
        # On a cluster, CPUs and the memory budget come from the SLURM allocation.
        self._remote_note = ""
        if background:
            args.append('--background')
        self.background_check.setEnabled(False)
        self.solve_detail.clear()
        self.stages.start("starting…")
        scs_job_service.service().submit(self.doc, 'Solve', self.solve_runner, args, self.env_overrides())
        self.refresh_gates()

    def on_plot_button(self):
        try:
            self.sync_waveform()
        except ValueError as exc:
            self.stages.set_caption(str(exc), scs_stages.FAIL_FG)
            return
        run_dir = self.prepare_run()
        if run_dir is None:
            return
        background = self.background_check.isChecked()
        if not live_lead.field_ready(run_dir, background):
            self.refresh_gates()
            return
        sol_npz = os.path.join(run_dir, "solution_bg.npz" if background else "solution.npz")
        if sol_npz != self._current_sol_npz and not self.bind_field(sol_npz):
            return
        self.apply_montage()

    def on_plot_solve_progress(self, pct):
        self.stages.progress(pct)

    def on_solve_stage(self, message):
        self.solve_detail.appendPlainText(message)
        if message.startswith("HPC: "):
            self._remote_note = message[len("HPC: "):]

    def on_solve_tick(self, _elapsed):
        svc = scs_job_service.service()
        ident = next((i for i, r in svc.runners.items() if r is self.solve_runner), None)
        if ident:
            self.stages.attach(ident, svc.records[ident].get("created"))
        self.stages.tick(self._remote_note)
        self.stages.set_resources(scs_monitor.monitor().line(ident) if ident else "")

    def on_plot_solve_finished(self, report):
        self.background_check.setEnabled(True)
        self.solve_detail.setPlainText(report.get("_stdout_tail", ""))
        live_lead.save_report(self._pending_run_dir, "solve_report", report)
        # Plot straight away only if currents are already set; a solve needs none.
        if self.bind_field(report["solution_npz"]) and any(s.value() for s in self.contact_spins):
            self.apply_montage()

    def on_plot_failed(self, msg):
        self.solve_detail.setPlainText(msg)
        self.log_toggle.setChecked(True)
        self.stages.failed("Solve failed: " + msg.splitlines()[0])
        self.background_check.setEnabled(True)
        self._aborting = False
        self._gate = "failed"
        self.refresh_gates()

    def on_plot_aborted(self, msg):
        self.stages.failed(msg)
        self.background_check.setEnabled(True)
        self._aborting = False
        self._gate = "failed"
        self.refresh_gates()

    def bind_field(self, sol_npz):
        """Make sol_npz, solved for the CURRENT live lead, the field to plot.
        First the montage arithmetic's self check (the default bipolar case's
        general-path V against the solve's own stored V -- run on the cluster,
        beside the solution, when the solution stayed there)."""
        current_info, current_run = self.resolve_run()
        if current_run != self._pending_run_dir:
            self.on_plot_failed('Lead geometry or mesh settings changed during solve. Generate/select the matching mesh first.')
            return False
        try:
            ok, msg = M.self_check(sol_npz=sol_npz)
        except Exception as exc:
            ok, msg = False, str(exc)
        if not ok:
            self.on_plot_failed("Montage self-check failed for this solution: %s" % msg)
            return False
        self._current_sol_npz = sol_npz
        self.montage_obj.SolutionNpz = sol_npz
        self._gate = None
        self.refresh_gates()
        return True

    # -- combine (fast, synchronous -- no FEM solve here) ------------------
    def apply_montage(self):
        if self._current_sol_npz is None or self.busy():
            return
        currents = [spin.value() for spin in self.contact_spins]
        clamp_v = self.clamp_spin.value()
        QtWidgets.QApplication.setOverrideCursor(QtCore.Qt.WaitCursor)
        try:
            self.sync_waveform()
            for i, val in enumerate(currents, start=1):
                setattr(self.montage_obj, "Contact%d_mA" % i, float(val))
            self.montage_obj.ClampVolts = float(clamp_v)
            revision = self.montage_obj.PlotRevision
            self.montage_obj.touch()
            self.doc.recompute([self.montage_obj])
            if self.montage_obj.PlotRevision == revision:
                raise RuntimeError(self.montage_obj.Status)
            stats = self.montage_obj.Proxy._last_stats
        except Exception as exc:
            QtWidgets.QApplication.restoreOverrideCursor()
            self.stages.set_caption("Plot failed: %s" % exc, scs_stages.FAIL_FG)
            return
        QtWidgets.QApplication.restoreOverrideCursor()
        for pipe in self.pipes.values():
            pipe.ViewObject.Visibility = True
        self.refresh_readout(stats)
        self.readout.setToolTip(str(self.montage_obj.Status))

    def refresh_readout(self, stats):
        charge = stats.get("source_mA", 0)-stats.get("sink_mA", 0)
        scale = max(1.0, max(abs(s.value()) for s in self.contact_spins))
        balanced = abs(charge) < 1e-6 * scale
        phase = self.phase_choice.currentText().lower() if self.wave_mode.currentText() != 'Static' else ''
        bits = ["colour ±%.4g %s" % (stats["clamp_v"], self.unit()),
                "balanced" if balanced else "UNBALANCED by %.4g mA" % charge, phase]
        self.plot_line.setText(" · ".join(b for b in bits if b))
        self.plot_line.setStyleSheet("" if balanced else "color: %s; font-weight: bold;" % scs_stages.FAIL_FG)
        for t in M.TISSUES:
            s = stats["tissues"][t]
            txt = "%.3g … %.3g %s" % (s["v_min"], s["v_max"], self.unit())
            if s["n_nan"]:
                txt += "  NaN %d" % s["n_nan"]
            self.tissue_labels[t].setText(txt)
        self.readout.setVisible(True)

    def on_dock_closing(self):
        self._poll_timer.stop()
        if self.solve_runner.is_running() and not scs_job_service.service().owns(self.solve_runner):
            self.solve_runner.abort()


def show_panel():
    doc = get_target_document()
    FreeCAD.setActiveDocument(doc.Name)
    FreeCADGui.setActiveDocument(doc.Name)

    mw = FreeCADGui.getMainWindow()
    dock = mw.findChild(QtWidgets.QDockWidget, OBJECT_NAME)
    if dock is None:
        dock = QtWidgets.QDockWidget("SCS Potential Visualizer", mw)
        dock.setObjectName(OBJECT_NAME)
        mw.addDockWidget(QtCore.Qt.RightDockWidgetArea, dock)
    else:
        old_widget = dock.widget()
        if old_widget is not None and hasattr(old_widget, 'busy') and old_widget.busy():
            dock.show()
            dock.raise_()
            print('A solve is running for ' + old_widget.doc.Label + '. Monitor it in Job Manager.')
            return dock
        if old_widget is not None and hasattr(old_widget, "on_dock_closing"):
            old_widget.on_dock_closing()
    old_widget = dock.widget()
    panel = PotentialVisualizerPanel(doc)
    dock.setWidget(panel)
    if old_widget is not None:
        old_widget.deleteLater()
    dock.show()
    dock.raise_()
    return dock


def main():
    show_panel()
    print(
        "Done. The SCS Potential Field Visualizer dock is open. Not saved "
        "-- File > Save if you want to keep this."
    )


if __name__ == "__main__":
    main()
